IBP DEFINITIONS ::= BEGIN

IMPORTS
	enterprises, IpAddress
		FROM RFC1155-SMI
	OBJECT-TYPE
		FROM RFC-1212
	TRAP-TYPE
		FROM RFC-1215
	DisplayString
		FROM RFC-1213;


-- Системы ПромАвтоматики

entSPA-SIB           OBJECT IDENTIFIER ::= { enterprises 33183 }
ibp                  OBJECT IDENTIFIER ::= { entSPA-SIB 25 }
displayDeviceInfo    OBJECT IDENTIFIER ::= { ibp 1 }
displayMainPower     OBJECT IDENTIFIER ::= { ibp 2 }
displayInverter      OBJECT IDENTIFIER ::= { ibp 3 }
displayBattery       OBJECT IDENTIFIER ::= { ibp 4 }
displayEnergyMeterImpuls  OBJECT IDENTIFIER ::= { ibp 6 }
displayEthernetSettings  OBJECT IDENTIFIER ::= { ibp 7 }
displaySNMPSettings  OBJECT IDENTIFIER ::= { ibp 8 }
displayWrkSettings   OBJECT IDENTIFIER ::= { ibp 9 }
displayHummidity     OBJECT IDENTIFIER ::= { ibp 10 }

displayDeviceSerial  OBJECT-TYPE
	SYNTAX     INTEGER (0..65535)
	ACCESS     read-only
	STATUS     mandatory
	DESCRIPTION 
		""
	::= { displayDeviceInfo 1 }

displayDeviceLocation  OBJECT-TYPE
	SYNTAX     DisplayString (SIZE(69))
	ACCESS     read-write
	STATUS     mandatory
	DESCRIPTION 
		""
	::= { displayDeviceInfo 2 }

displayDeviceInfoResetCounter  OBJECT-TYPE
	SYNTAX     INTEGER
	ACCESS     read-write
	STATUS     mandatory
	DESCRIPTION 
		""
	::= { displayDeviceInfo 3 }

displayMainVoltage  OBJECT-TYPE
	SYNTAX     INTEGER (0..65535)
	ACCESS     read-only
	STATUS     mandatory
	DESCRIPTION 
		""
	::= { displayMainPower 1 }

displayMainPowerOnOff  OBJECT-TYPE
	SYNTAX     INTEGER
	ACCESS     read-only
	STATUS     mandatory
	DESCRIPTION 
		""
	::= { displayMainPower 2 }

displayInverterVoltage  OBJECT-TYPE
	SYNTAX     INTEGER (0..65535)
	ACCESS     read-only
	STATUS     mandatory
	DESCRIPTION 
		""
	::= { displayInverter 1 }

displayInverterCurrent  OBJECT-TYPE
	SYNTAX     INTEGER (0..65535)
	ACCESS     read-only
	STATUS     mandatory
	DESCRIPTION 
		""
	::= { displayInverter 2 }

displayInverterTemperature  OBJECT-TYPE
	SYNTAX     INTEGER (0..65535)
	ACCESS     read-only
	STATUS     mandatory
	DESCRIPTION 
		""
	::= { displayInverter 3 }

displayBatteryVoltage  OBJECT-TYPE
	SYNTAX     INTEGER
	ACCESS     read-only
	STATUS     mandatory
	DESCRIPTION 
		""
	::= { displayBattery 1 }

displayBatteryCurrent  OBJECT-TYPE
	SYNTAX     INTEGER
	ACCESS     read-only
	STATUS     mandatory
	DESCRIPTION 
		""
	::= { displayBattery 2 }

displayImpulseEnergyMeter  OBJECT-TYPE
	SYNTAX     INTEGER
	ACCESS     read-write
	STATUS     mandatory
	DESCRIPTION 
		""
	::= { displayEnergyMeterImpuls 1 }

displayImpulsEnergyMeterTotalEnergy  OBJECT-TYPE
	SYNTAX     INTEGER
	ACCESS     read-only
	STATUS     mandatory
	DESCRIPTION 
		""
	::= { displayEnergyMeterImpuls 2 }

displayImpulsEnergyMeterImpulsPerKwth  OBJECT-TYPE
	SYNTAX     INTEGER
	ACCESS     read-write
	STATUS     mandatory
	DESCRIPTION 
		""
	::= { displayEnergyMeterImpuls 3 }

displayEthernetSettingsIPAddress  OBJECT-TYPE
	SYNTAX     IpAddress
	ACCESS     read-write
	STATUS     mandatory
	DESCRIPTION 
		""
	::= { displayEthernetSettings 1 }

displayEthernetSettingsNetMask  OBJECT-TYPE
	SYNTAX     IpAddress
	ACCESS     read-write
	STATUS     mandatory
	DESCRIPTION 
		""
	::= { displayEthernetSettings 2 }

displayEthernetSettingsDefGatw  OBJECT-TYPE
	SYNTAX     IpAddress
	ACCESS     read-write
	STATUS     mandatory
	DESCRIPTION 
		""
	::= { displayEthernetSettings 3 }

displaySNMPSettingsReadPort  OBJECT-TYPE
	SYNTAX     INTEGER
	ACCESS     read-write
	STATUS     mandatory
	DESCRIPTION 
		""
	::= { displaySNMPSettings 1 }

displaySNMPSettingsWritePort  OBJECT-TYPE
	SYNTAX     INTEGER
	ACCESS     read-write
	STATUS     mandatory
	DESCRIPTION 
		""
	::= { displaySNMPSettings 2 }

displaySNMPSettingsReadCommunity  OBJECT-TYPE
	SYNTAX     OCTET STRING
	ACCESS     read-write
	STATUS     mandatory
	DESCRIPTION 
		""
	::= { displaySNMPSettings 3 }

displaySNMPSettingsWriteCommunity  OBJECT-TYPE
	SYNTAX     OCTET STRING
	ACCESS     read-write
	STATUS     mandatory
	DESCRIPTION 
		""
	::= { displaySNMPSettings 4 }

displaySNMPSettingsTrapServer1  OBJECT-TYPE
	SYNTAX     IpAddress
	ACCESS     read-write
	STATUS     mandatory
	DESCRIPTION 
		""
	::= { displaySNMPSettings 5 }

displaySNMPSettingsTrapServer2  OBJECT-TYPE
	SYNTAX     IpAddress
	ACCESS     read-write
	STATUS     mandatory
	DESCRIPTION 
		""
	::= { displaySNMPSettings 6 }

displaySNMPSettingsTrapServer3  OBJECT-TYPE
	SYNTAX     IpAddress
	ACCESS     read-write
	STATUS     mandatory
	DESCRIPTION 
		""
	::= { displaySNMPSettings 7 }

displaySNMPSettingsTrapServer4  OBJECT-TYPE
	SYNTAX     IpAddress
	ACCESS     read-write
	STATUS     mandatory
	DESCRIPTION 
		""
	::= { displaySNMPSettings 8 }

displaySNMPSettingsTrapServer5  OBJECT-TYPE
	SYNTAX     IpAddress
	ACCESS     read-write
	STATUS     mandatory
	DESCRIPTION 
		""
	::= { displaySNMPSettings 9 }

displayLogIn1StatOfAv  OBJECT-TYPE
	SYNTAX     INTEGER
	ACCESS     read-write
	STATUS     mandatory
	DESCRIPTION 
		""
	::= { displayWrkSettings 1 }

displayLogIn2StatOfAv  OBJECT-TYPE
	SYNTAX     INTEGER
	ACCESS     read-write
	STATUS     mandatory
	DESCRIPTION 
		""
	::= { displayWrkSettings 2 }

displayLogIn3StatOfAv  OBJECT-TYPE
	SYNTAX     INTEGER
	ACCESS     read-write
	STATUS     mandatory
	DESCRIPTION 
		""
	::= { displayWrkSettings 3 }

displayLogIn4StatOfAv  OBJECT-TYPE
	SYNTAX     INTEGER
	ACCESS     read-write
	STATUS     mandatory
	DESCRIPTION 
		""
	::= { displayWrkSettings 4 }

displayLogIn5StatOfAv  OBJECT-TYPE
	SYNTAX     INTEGER
	ACCESS     read-write
	STATUS     mandatory
	DESCRIPTION 
		""
	::= { displayWrkSettings 5 }

displayLogIn6StatOfAv  OBJECT-TYPE
	SYNTAX     INTEGER
	ACCESS     read-write
	STATUS     mandatory
	DESCRIPTION 
		""
	::= { displayWrkSettings 6 }

displayLogIn1TrapSendOfAv  OBJECT-TYPE
	SYNTAX     INTEGER
	ACCESS     read-write
	STATUS     mandatory
	DESCRIPTION 
		""
	::= { displayWrkSettings 7 }

displayLogIn2TrapSendOfAv  OBJECT-TYPE
	SYNTAX     INTEGER
	ACCESS     read-write
	STATUS     mandatory
	DESCRIPTION 
		""
	::= { displayWrkSettings 8 }

displayLogIn3TrapSendOfAv  OBJECT-TYPE
	SYNTAX     INTEGER
	ACCESS     read-write
	STATUS     mandatory
	DESCRIPTION 
		""
	::= { displayWrkSettings 9 }

displayLogIn4TrapSendOfAv  OBJECT-TYPE
	SYNTAX     INTEGER
	ACCESS     read-write
	STATUS     mandatory
	DESCRIPTION 
		""
	::= { displayWrkSettings 10 }

displayLogIn5TrapSendOfAv  OBJECT-TYPE
	SYNTAX     INTEGER
	ACCESS     read-write
	STATUS     mandatory
	DESCRIPTION 
		""
	::= { displayWrkSettings 11 }

displayLogIn6TrapSendOfAv  OBJECT-TYPE
	SYNTAX     INTEGER
	ACCESS     read-write
	STATUS     mandatory
	DESCRIPTION 
		""
	::= { displayWrkSettings 12 }

displayLogIn1TrapSendOfNoAv  OBJECT-TYPE
	SYNTAX     INTEGER
	ACCESS     read-write
	STATUS     mandatory
	DESCRIPTION 
		""
	::= { displayWrkSettings 13 }

displayLogIn2TrapSendOfNoAv  OBJECT-TYPE
	SYNTAX     INTEGER
	ACCESS     read-write
	STATUS     mandatory
	DESCRIPTION 
		""
	::= { displayWrkSettings 14 }

displayLogIn3TrapSendOfNoAv  OBJECT-TYPE
	SYNTAX     INTEGER
	ACCESS     read-write
	STATUS     mandatory
	DESCRIPTION 
		""
	::= { displayWrkSettings 15 }

displayLogIn4TrapSendOfNoAv  OBJECT-TYPE
	SYNTAX     INTEGER
	ACCESS     read-write
	STATUS     mandatory
	DESCRIPTION 
		""
	::= { displayWrkSettings 16 }

displayLogIn5TrapSendOfNoAv  OBJECT-TYPE
	SYNTAX     INTEGER
	ACCESS     read-write
	STATUS     mandatory
	DESCRIPTION 
		""
	::= { displayWrkSettings 17 }

displayLogIn6TrapSendOfNoAv  OBJECT-TYPE
	SYNTAX     INTEGER
	ACCESS     read-write
	STATUS     mandatory
	DESCRIPTION 
		""
	::= { displayWrkSettings 18 }

displayHummidityTrapSendOfAv  OBJECT-TYPE
	SYNTAX     INTEGER
	ACCESS     read-write
	STATUS     mandatory
	DESCRIPTION 
		""
	::= { displayWrkSettings 19 }

displayHummidityTrapSendOfNoAv  OBJECT-TYPE
	SYNTAX     INTEGER
	ACCESS     read-write
	STATUS     mandatory
	DESCRIPTION 
		""
	::= { displayWrkSettings 20 }

displayHummiditySensor  OBJECT-TYPE
	SYNTAX     INTEGER
	ACCESS     read-only
	STATUS     mandatory
	DESCRIPTION 
		""
	::= { displayHummidity 1 }

displayAlarmHummidityLevel  OBJECT-TYPE
	SYNTAX     INTEGER
	ACCESS     read-write
	STATUS     mandatory
	DESCRIPTION 
		""
	::= { displayHummidity 2 }

displayAlarmHummidityLogic  OBJECT-TYPE
	SYNTAX     INTEGER
	ACCESS     read-write
	STATUS     mandatory
	DESCRIPTION 
		""
	::= { displayHummidity 3 }

displayAlarmHummidityStatus  OBJECT-TYPE
	SYNTAX     INTEGER
	ACCESS     read-only
	STATUS     mandatory
	DESCRIPTION 
		""
	::= { displayHummidity 4 }

displayAlarmHummidityTrapSendAv  OBJECT-TYPE
	SYNTAX     INTEGER
	ACCESS     read-write
	STATUS     mandatory
	DESCRIPTION 
		""
	::= { displayHummidity 5 }

displayAlarmHummidityTrapSendNoAv  OBJECT-TYPE
	SYNTAX     INTEGER
	ACCESS     read-write
	STATUS     mandatory
	DESCRIPTION 
		""
	::= { displayHummidity 6 }

alarmTrap  TRAP-TYPE
	ENTERPRISE entSPA-SIB
	DESCRIPTION 
		""
	::= 3
END


-- This MIB was created using NuDesign Team's Visual MIBuilder (Ver 4.7).
